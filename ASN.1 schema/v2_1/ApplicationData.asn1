ApplicationDataModule

DEFINITIONS
AUTOMATIC TAGS ::= 
BEGIN
MP_SecurityAlarmResp ::= SEQUENCE
{
  securityAlarms SEQUENCE SIZE(1..256) OF SecurityAlarm OPTIONAL
}
OTA_RVMVehicleStatusReq ::= SEQUENCE
{
  vehStatusReqType INTEGER(0..255)
}
OTA_RVMVehicleStatusResp25857 ::= SEQUENCE
{
  statusTime INTEGER(0..2147483647),
  gpsPosition RvsPosition(1),
  basicVehicleStatus RvsBasicStatus25857(1),
  extendedVehicleStatus RvsExtStatus(1) OPTIONAL
}
OTA_RVMVehicleClassifiedStatusReq ::= SEQUENCE
{
  rvmClassifiedType OCTET STRING(SIZE(1..100)),
  vehStatusReqType INTEGER(0..255)
}
OTA_RVMVehicleClassifiedStatusResp25857 ::= SEQUENCE
{
  statusTime INTEGER(0..2147483647),
  gpsPosition RvsPosition(1) OPTIONAL,
  rvmParams SEQUENCE SIZE(1..1000) OF RvsStatusParam,
  basicVehicleStatus RvsBasicStatus25857(1) OPTIONAL,
  extendedVehicleStatus RvsExtStatus(1) OPTIONAL
}
OTA_RVCReq ::= SEQUENCE
{
  rvcReqType OCTET STRING(SIZE(1)),
  rvcParams SEQUENCE SIZE(1..10) OF RvcReqParam OPTIONAL
}
OTA_RVCStatus25857 ::= SEQUENCE
{
  rvcReqType OCTET STRING(SIZE(1)),
  rvcReqSts OCTET STRING(SIZE(1)),
  failureType INTEGER(0..255) OPTIONAL,
  gpsPosition RvsPosition(1),
  basicVehicleStatus RvsBasicStatus25857(1)
}
SecurityAlarm ::= SEQUENCE
{
  title OCTET STRING(SIZE(1..128)) OPTIONAL,
  content OCTET STRING(SIZE(1..2048)) OPTIONAL,
  messageType IA5String(SIZE(3)),
  vin IA5String(SIZE(17)),
  alertId INTEGER(0..65535),
  alertTime INTEGER(0..2147483647) OPTIONAL,
  latitude INTEGER(-90000000..90000000),
  longitude INTEGER(-180000000..180000000)
}
RvsPosition ::= SEQUENCE
{
  wayPoint RvsWayPoint,
  timestamp4Short Timestamp4Short,
  gpsStatus GPSStatus
}
RvsBasicStatus25857 ::= SEQUENCE
{
  driverDoor BOOLEAN,
  passengerDoor BOOLEAN,
  rearLeftDoor BOOLEAN,
  rearRightDoor BOOLEAN,
  bootStatus BOOLEAN,
  bonnetStatus BOOLEAN,
  lockStatus BOOLEAN,
  driverWindow BOOLEAN OPTIONAL,
  passengerWindow BOOLEAN OPTIONAL,
  rearLeftWindow BOOLEAN OPTIONAL,
  rearRightWindow BOOLEAN OPTIONAL,
  sunroofStatus BOOLEAN OPTIONAL,
  frontRrightTyrePressure INTEGER(0..255) OPTIONAL,
  frontLeftTyrePressure INTEGER(0..255) OPTIONAL,
  rearRightTyrePressure INTEGER(0..255) OPTIONAL,
  rearLeftTyrePressure INTEGER(0..255) OPTIONAL,
  wheelTyreMonitorStatus  INTEGER(0..255) OPTIONAL,
  sideLightStatus BOOLEAN,
  dippedBeamStatus BOOLEAN,
  mainBeamStatus BOOLEAN,
  vehicleAlarmStatus INTEGER(0..255) OPTIONAL,
  engineStatus INTEGER(0..255),
  powerMode INTEGER(0..255),
  lastKeySeen INTEGER(0..65535),
  currentjourneyDistance INTEGER(0..65535),
  currentJourneyID INTEGER(0..2147483647),
  interiorTemperature INTEGER(-128..127),
  exteriorTemperature INTEGER(-128..127),
  fuelLevelPrc INTEGER(0..255),
  fuelRange INTEGER(0..65535),
  remoteClimateStatus INTEGER(0..255),
  frontLeftSeatHeatLevel INTEGER(0..255) OPTIONAL,
  frontRightSeatHeatLevel INTEGER(0..255) OPTIONAL,
  canBusActive BOOLEAN,
  timeOfLastCANBUSActivity INTEGER(0..2147483647),
  clstrDspdFuelLvlSgmt INTEGER(0..255),
  mileage INTEGER(0..2147483647),
  batteryVoltage INTEGER(0..65535),
  handBrake BOOLEAN,
  vehElecRngDsp INTEGER(0..255),
  fuelRangeElec INTEGER(0..65535) OPTIONAL,
  rmtHtdRrWndSt INTEGER(0..255),
  extendedData1 INTEGER(0..2147483647) OPTIONAL,
  extendedData2 INTEGER(0..2147483647) OPTIONAL
}
RvsExtStatus ::= SEQUENCE
{
  vehicleAlerts SEQUENCE SIZE(0..64) OF VehicleAlertInfo
}
RvsStatusParam ::= SEQUENCE
{
  paramId INTEGER(0..65535),
  paramValue OCTET STRING(SIZE(1..255))
}
RvcReqParam ::= SEQUENCE
{
  paramId INTEGER(0..65535),
  paramValue OCTET STRING(SIZE(1..255))
}
RvsWayPoint ::= SEQUENCE
{
  position RvsWGS84Point,
  heading INTEGER(0..359),
  speed INTEGER(-1000..4500),
  hdop INTEGER(0..1000),
  satellites INTEGER(0..16)
}
Timestamp4Short ::= SEQUENCE
{
  seconds INTEGER(0..2147483647)
}
GPSStatus ::= ENUMERATED
{
  noGpsSignal(0),
  timeFix(1),
  fix2D(2),
  fix3D(3)
}
VehicleAlertInfo ::= SEQUENCE
{
  id INTEGER(0..255),
  value INTEGER(0..255)
}
RvsWGS84Point ::= SEQUENCE
{
  latitude INTEGER(-90000000..90000000),
  longitude INTEGER(-180000000..180000000),
  altitude INTEGER(-100..8900)
}

END
